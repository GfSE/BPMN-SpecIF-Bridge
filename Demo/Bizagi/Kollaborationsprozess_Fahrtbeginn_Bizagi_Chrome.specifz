# Kollaborationsprozess_Fahrtbeginn_Bizagi_Chrome
DefaultDescription

## Fahrtbeginn als BPMN-Modell in Signavio (SpecIF:Diagram)
- SpecIF:Diagram: Dies ist der hochgeladene BPMN-Prozess
  Model View:
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- SpecIF:Notation: BPMN 2.0 Process Diagram

## Fahrer (FMC:Actor)
- SpecIF:Stereotype: participant

## Roller gestartet! (FMC:Event)
- SpecIF:Stereotype: startEvent

## Auftragsdaten synchronisieren (FMC:Actor)
- SpecIF:Stereotype: task

## Fahrt abgebrochen! (FMC:Event)
- SpecIF:Stereotype: endEvent

## Auftrag auswählen (FMC:Actor)
- SpecIF:Stereotype: task

## Empfänger kontaktieren (FMC:Actor)
- SpecIF:Stereotype: task

## Route berechnen (FMC:Actor)
- SpecIF:Stereotype: task

## Mit Roller losfahren (FMC:Actor)
- SpecIF:Stereotype: task

## Fahrt begonnen! (FMC:Event)
- SpecIF:Stereotype: endEvent

## Server nicht erreichbar (FMC:Event)
- SpecIF:Stereotype: exklusiveGateway

## Server erreichbar (FMC:Event)
- SpecIF:Stereotype: exklusiveGateway

## Warte auf vorherige Elemente (FMC:Actor)
- SpecIF:Stereotype: parallelGateway

## Fleetmanagementsystem (FMC:Actor)
- SpecIF:Stereotype: participant

## Empfänger (FMC:Actor)
- SpecIF:Stereotype: participant

## Anfrage (FMC:State)
- SpecIF:Stereotype: messageFlow

## Auftragsdaten (FMC:State)
- SpecIF:Stereotype: messageFlow

## Versandbestätigung (FMC:State)
- SpecIF:Stereotype: messageFlow

## Modell-Elemente (Glossar) (SpecIF:Heading)

## Akteure (SpecIF:Heading)

## Zustände (SpecIF:Heading)

## Ereignisse (SpecIF:Heading)

## Statements
- Roller gestartet! SpecIF:triggers Auftragsdaten synchronisieren
- Mit Roller losfahren SpecIF:signals Fahrt begonnen!
- Auftragsdaten synchronisieren SpecIF:signals Server nicht erreichbar
- Server nicht erreichbar SpecIF:signals Fahrt abgebrochen!
- Auftragsdaten synchronisieren SpecIF:signals Server erreichbar
- Server erreichbar SpecIF:triggers Auftrag auswählen
- Auftrag auswählen SpecIF:precedes Empfänger kontaktieren
- Auftrag auswählen SpecIF:precedes Route berechnen
- Warte auf vorherige Elemente SpecIF:precedes Mit Roller losfahren
- Route berechnen SpecIF:precedes Warte auf vorherige Elemente
- Empfänger kontaktieren SpecIF:precedes Warte auf vorherige Elemente
- Fahrer SpecIF:contains Roller gestartet!
- Fahrer SpecIF:contains Auftragsdaten synchronisieren
- Fahrer SpecIF:contains Fahrt abgebrochen!
- Fahrer SpecIF:contains Auftrag auswählen
- Fahrer SpecIF:contains Empfänger kontaktieren
- Fahrer SpecIF:contains Route berechnen
- Fahrer SpecIF:contains Mit Roller losfahren
- Fahrer SpecIF:contains Fahrt begonnen!
- Fahrer SpecIF:contains Server nicht erreichbar
- Fahrer SpecIF:contains Server erreichbar
- Fahrer SpecIF:contains Warte auf vorherige Elemente
- Auftragsdaten synchronisieren SpecIF:writes Anfrage
- Fleetmanagementsystem SpecIF:reads Anfrage
- Fahrer SpecIF:contains Anfrage
- Fleetmanagementsystem SpecIF:contains Anfrage
- Fleetmanagementsystem SpecIF:writes Auftragsdaten
- Auftragsdaten synchronisieren SpecIF:reads Auftragsdaten
- Fleetmanagementsystem SpecIF:contains Auftragsdaten
- Fahrer SpecIF:contains Auftragsdaten
- Empfänger kontaktieren SpecIF:writes Versandbestätigung
- Empfänger SpecIF:reads Versandbestätigung
- Fahrer SpecIF:contains Versandbestätigung
- Empfänger SpecIF:contains Versandbestätigung
- Fahrtbeginn als BPMN-Modell in Signavio SpecIF:shows Fahrer
- Fahrtbeginn als BPMN-Modell in Signavio SpecIF:shows Roller gestartet!
- Fahrtbeginn als BPMN-Modell in Signavio SpecIF:shows Auftragsdaten synchronisieren
- Fahrtbeginn als BPMN-Modell in Signavio SpecIF:shows Fahrt abgebrochen!
- Fahrtbeginn als BPMN-Modell in Signavio SpecIF:shows Auftrag auswählen
- Fahrtbeginn als BPMN-Modell in Signavio SpecIF:shows Empfänger kontaktieren
- Fahrtbeginn als BPMN-Modell in Signavio SpecIF:shows Route berechnen
- Fahrtbeginn als BPMN-Modell in Signavio SpecIF:shows Mit Roller losfahren
- Fahrtbeginn als BPMN-Modell in Signavio SpecIF:shows Fahrt begonnen!
- Fahrtbeginn als BPMN-Modell in Signavio SpecIF:shows Server nicht erreichbar
- Fahrtbeginn als BPMN-Modell in Signavio SpecIF:shows Server erreichbar
- Fahrtbeginn als BPMN-Modell in Signavio SpecIF:shows Warte auf vorherige Elemente
- Fahrtbeginn als BPMN-Modell in Signavio SpecIF:shows Fleetmanagementsystem
- Fahrtbeginn als BPMN-Modell in Signavio SpecIF:shows Empfänger
- Fahrtbeginn als BPMN-Modell in Signavio SpecIF:shows Anfrage
- Fahrtbeginn als BPMN-Modell in Signavio SpecIF:shows Auftragsdaten
- Fahrtbeginn als BPMN-Modell in Signavio SpecIF:shows Versandbestätigung
